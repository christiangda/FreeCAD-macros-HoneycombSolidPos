"""
HoneycombSolidPos --> Positive Honeycomb solid box mesh creator.
(c) 2021 Christian González Di Antonio <christiangda@gmail.com>

"""

__Name__ = 'HoneycombSolidPos'
__Comment__ = 'Macro to create a Positive Honeycomb solid box mesh'
__Author__ = "Christian González Di Antonio <christiangda@gmail.com>"
__Version__ = "v1.0.0"
__License__ = 'LGPL-2.0-or-later'
__Web__ = "https://github.com/christiangda/FreeCAD-macros-HoneycombSolidPos"
__Wiki__ = "https://github.com/christiangda/FreeCAD-macros-HoneycombSolidPos/blob/main/README.md"
__Icon__ = ''
__Help__ = ''
__Status__ = 'Stable'
__Requires__ = ''
__Communication__ = 'https://github.com/FreeCAD/FreeCAD-macros/issues/'
__Files__ = 'honeycomb_solid_pos/__init__.py,honeycomb_solid_pos/honeycomb_solid_pos.py'

import FreeCAD as app
import FreeCADGui as gui

if __name__ == '__main__':
	try:
		from honeycomb_solid_pos.honeycomb_solid_pos import HoneycombSolidPos
		from honeycomb_solid_pos.honeycomb_solid_pos import ViewProviderHoneycombSolidPos
	except ImportError as err:
		app.Console.PrintError("Macro HoneycombSolidPos: failed to import Macro honeycomb_solid_pos.honeycomb_solid_pos.py. The parametric object will lose functionality after saving-loading your project, sorry.")
	else:
		from honeycomb_solid_pos.honeycomb_solid_pos import makeHoneycombSolidPos
		makeHoneycombSolidPos(__Version__)
		gui.SendMsgToActiveView("ViewFit")
